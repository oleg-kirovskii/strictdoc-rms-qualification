[DOCUMENT]
TITLE: RMS requirements

[GRAMMAR]
ELEMENTS:
- TAG: REQUIREMENT
  FIELDS:
  - TITLE: UID
    TYPE: String
    REQUIRED: True
  - TITLE: STATEMENT
    TYPE: String
    REQUIRED: True
  - TITLE: REFERENCES
    TYPE: String
    REQUIRED: True
  - TITLE: MALFORMED
    TYPE: SingleChoice(Yes, No)
    REQUIRED: True
  - TITLE: IMPLEMENTED
    TYPE: SingleChoice(Yes, No)
    REQUIRED: False

[REQUIREMENT]
UID: RMS-002
STATEMENT: RMS shall allow storing and managing documentation captured during interviews, workshops, and observations.
REFERENCES: 5.2.2 Requirements capture
MALFORMED: No

[REQUIREMENT]
UID: RMS-003
STATEMENT: RMS shall allow capturing and storing stakeholder information including name, role, responsibilities, and comments.
REFERENCES: 5.2.2 Requirements capture
MALFORMED: No

[REQUIREMENT]
UID: RMS-004
STATEMENT: RMS shall allow creating hierarchical relationships between requirements.
REFERENCES: 5.2.2 Requirements capture
MALFORMED: No

[REQUIREMENT]
UID: RMS-005
STATEMENT: RMS shall allow associating design rationale directly with hierarchical requirement links.
REFERENCES: 5.2.2 Requirements capture
MALFORMED: No

[REQUIREMENT]
UID: RMS-006
STATEMENT: RMS shall allow tracing requirements to stakeholders and generating traceability reports.
REFERENCES: 5.2.2 Requirements capture
MALFORMED: No

[REQUIREMENT]
UID: RMS-007
STATEMENT: RMS shall allow flexible bi-directional traceability between user needs, business requirements, and functional/quality requirements.
REFERENCES: 5.2.4 Stakeholder and requirements traceability
MALFORMED: No

[REQUIREMENT]
UID: RMS-008
STATEMENT: RMS shall allow capturing both "as-is" and "to-be" system elements, including graphics and text.
REFERENCES: 5.2.3 Capturing as-is and to-be
MALFORMED: No

[REQUIREMENT]
UID: RMS-009
STATEMENT: RMS shall allow storing and managing attributes for classifying requirements (e.g., status, criticality).
REFERENCES: 5.2.2 Requirements capture
MALFORMED: No

[REQUIREMENT]
UID: RMS-010
STATEMENT: RMS shall allow flexible search of requirements by identifier, keyword, or attribute.
REFERENCES: 5.2.2 Requirements capture
MALFORMED: No

[REQUIREMENT]
UID: RMS-011
STATEMENT: RMS shall allow importing and exporting requirements in standard formats (e.g., CSV, XML).
REFERENCES: 5.2.8 Import/export
MALFORMED: No

[REQUIREMENT]
UID: RMS-012
STATEMENT: RMS shall allow updating linked documents when new or changed versions are imported.
REFERENCES: 5.2.2 Requirements capture
MALFORMED: No

[REQUIREMENT]
UID: RMS-013
STATEMENT: RMS shall allow using elicitation templates, checklists, and prioritization forms.
REFERENCES: 5.2.6 Templates and checklists
MALFORMED: No

[REQUIREMENT]
UID: RMS-014
STATEMENT: RMS shall allow storing user-defined goal-oriented scenarios and business models.
REFERENCES: 5.2.5 Goal-oriented scenarios
MALFORMED: Yes

[REQUIREMENT]
UID: RMS-015
STATEMENT: RMS shall allow supporting prototyping of requirements with graphical interfaces.
REFERENCES: 5.2.7 Prototyping
MALFORMED: Yes

[REQUIREMENT]
UID: RMS-016
STATEMENT: RMS shall allow documenting elicitation outputs in text and non-text formats (graphics, tables, equations).
REFERENCES: 5.2.9 Elicitation documentation
MALFORMED: No

[REQUIREMENT]
UID: RMS-017
STATEMENT: RMS shall allow decomposition of high-level requirements into functional and quality requirements.
REFERENCES: 5.3.1 Overview
MALFORMED: No

[REQUIREMENT]
UID: RMS-018
STATEMENT: RMS shall allow linking requirements to implementation elements such as design architecture or work breakdown structures.
REFERENCES: 5.3.2 Functional reqs analysis
MALFORMED: No

[REQUIREMENT]
UID: RMS-019
STATEMENT: RMS shall allow modeling requirements using standard diagrams (e.g., UML, data flow, entity-relationship).
REFERENCES: 5.3.5 Modeling
MALFORMED: Yes

[REQUIREMENT]
UID: RMS-020
STATEMENT: RMS shall allow importing and exporting models to and from external modeling tools.
REFERENCES: 5.3.5 Modeling
MALFORMED: No

[REQUIREMENT]
UID: RMS-021
STATEMENT: RMS shall allow storing feasibility analysis results, including rationale and checklists.
REFERENCES: 5.3.4 Feasibility analysis
MALFORMED: Yes

[REQUIREMENT]
UID: RMS-022
STATEMENT: RMS shall allow associating requirements with identified risks for mitigation tracking.
REFERENCES: 5.3.9 Risk analysis
MALFORMED: No

[REQUIREMENT]
UID: RMS-023
STATEMENT: RMS shall allow managing requirement attributes such as risk, priority, and cost.
REFERENCES: 5.3.7 Attribute analysis
MALFORMED: Yes

[REQUIREMENT]
UID: RMS-024
STATEMENT: RMS shall allow detecting and flagging missing attributes on requirements.
REFERENCES: 5.3.7 Attribute analysis
MALFORMED: No

[REQUIREMENT]
UID: RMS-025
STATEMENT: RMS shall allow storing conflicts among requirements with their resolutions and rationale.
REFERENCES: 5.3.10 Decision methods
MALFORMED: No

[REQUIREMENT]
UID: RMS-026
STATEMENT: RMS shall allow recording rationale for requirement refinement and allocation.
REFERENCES: 5.3.8 Requirements refinement
MALFORMED: No

[REQUIREMENT]
UID: RMS-027
STATEMENT: RMS shall allow prototyping of ambiguous or uncertain requirements via GUIs and algorithm demonstrations.
REFERENCES: 5.3.6 Prototyping
MALFORMED: Yes

[REQUIREMENT]
UID: RMS-028
STATEMENT: RMS shall allow documenting analysis artifacts in both text and graphical formats.
REFERENCES: 5.3.11 Requirements analysis artifacts
MALFORMED: No

[REQUIREMENT]
UID: RMS-029
STATEMENT: RMS shall allow documenting requirements in a consistent and reviewable way.
REFERENCES: 5.4.1 Overview
MALFORMED: No

[REQUIREMENT]
UID: RMS-030
STATEMENT: RMS shall allow generating traceability matrices linking requirements to sources, analyses, design elements, and test cases.
REFERENCES: 5.4.3 Traceability analysis
MALFORMED: No

[REQUIREMENT]
UID: RMS-031
STATEMENT: RMS shall allow generating reports on orphan requirements and inconsistencies in traceability.
REFERENCES: 5.4.3 Traceability analysis
MALFORMED: No

[REQUIREMENT]
UID: RMS-032
STATEMENT: RMS shall allow generating and exporting user-defined or standard specification templates.
REFERENCES: 5.4.2 Developing specification
MALFORMED: No

[REQUIREMENT]
UID: RMS-033
STATEMENT: RMS shall allow performing spell checking and grammar checking of requirements statements.
REFERENCES: 5.4.4 Specification documentation
MALFORMED: No

[REQUIREMENT]
UID: RMS-034
STATEMENT: RMS shall allow documenting constraints, assumptions, and rationale linked to requirements.
REFERENCES: 5.4.4 Specification documentation
MALFORMED: No

[REQUIREMENT]
UID: RMS-035
STATEMENT: RMS shall allow generating reports on exceptions between user requirements and functional requirements.
REFERENCES: 5.4.2 Developing specification
MALFORMED: Yes

[REQUIREMENT]
UID: RMS-036
STATEMENT: RMS shall allow generating presentation-quality charts and graphs.
REFERENCES: 5.4.4 Specification documentation
MALFORMED: Yes

[REQUIREMENT]
UID: RMS-037
STATEMENT: RMS shall allow synchronizing changes between RMS and formatted specification documents.
REFERENCES: 5.4.4 Specification documentation
MALFORMED: No

[REQUIREMENT]
UID: RMS-038
STATEMENT: RMS shall allow exporting specification documents in common formats (RTF, MS Word, PDF).
REFERENCES: 5.4.4 Specification documentation
MALFORMED: No

[REQUIREMENT]
UID: RMS-039
STATEMENT: RMS shall allow unique identification and numbering of every requirement.
REFERENCES: 5.4.4 Specification documentation
MALFORMED: No

[REQUIREMENT]
UID: RMS-040
STATEMENT: RMS shall allow linking requirements to verification cases.
REFERENCES: 5.5.3 Verification
MALFORMED: No

[REQUIREMENT]
UID: RMS-041
STATEMENT: RMS shall allow linking requirements to validation cases.
REFERENCES: 5.5.4 Validation
MALFORMED: No

[REQUIREMENT]
UID: RMS-042
STATEMENT: RMS shall allow tracing verification cases to verification procedures.
REFERENCES: 5.5.3 Verification
MALFORMED: No

[REQUIREMENT]
UID: RMS-043
STATEMENT: RMS shall allow tracing validation cases to validation procedures.
REFERENCES: 5.5.4 Validation
MALFORMED: No

[REQUIREMENT]
UID: RMS-044
STATEMENT: RMS shall allow generating exception reports for requirements without verification cases.
REFERENCES: 5.5.3 Verification
MALFORMED: Yes

[REQUIREMENT]
UID: RMS-045
STATEMENT: RMS shall allow generating exception reports for requirements without validation cases.
REFERENCES: 5.5.4 Validation
MALFORMED: No

[REQUIREMENT]
UID: RMS-046
STATEMENT: RMS shall allow managing review and inspection comments linked to requirements.
REFERENCES: 5.5.2 Review and inspection
MALFORMED: No

[REQUIREMENT]
UID: RMS-047
STATEMENT: RMS shall allow storing and managing verification and validation plans and procedures.
REFERENCES: 5.5.3/5.5.4 Verification & Validation
MALFORMED: No

[REQUIREMENT]
UID: RMS-048
STATEMENT: RMS shall allow storing and managing acceptance criteria linked to requirements.
REFERENCES: 5.5.5 Defining acceptance criteria
MALFORMED: No

[REQUIREMENT]
UID: RMS-049
STATEMENT: RMS shall allow generating exception reports for requirements lacking acceptance criteria.
REFERENCES: 5.5.5 Defining acceptance criteria
MALFORMED: No

[REQUIREMENT]
UID: RMS-050
STATEMENT: RMS shall allow generating exception reports for design elements or interfaces not traced to requirements.
REFERENCES: 5.5.5 Defining acceptance criteria
MALFORMED: Yes

[REQUIREMENT]
UID: RMS-051
STATEMENT: RMS shall allow generating baseline sets of requirements once approved by stakeholders.
REFERENCES: 5.5.6 Baselines
MALFORMED: No

[REQUIREMENT]
UID: RMS-052
STATEMENT: RMS shall allow tracing baselines to specific product releases.
REFERENCES: 5.5.6 Baselines
MALFORMED: No

[REQUIREMENT]
UID: RMS-053
STATEMENT: RMS shall allow version-controlling baselines and generating comparison reports.
REFERENCES: 5.5.6 Baselines
MALFORMED: No

[REQUIREMENT]
UID: RMS-054
STATEMENT: RMS shall allow enforcing read/write protection on baseline requirements.
REFERENCES: 5.5.6 Baselines
MALFORMED: No

[REQUIREMENT]
UID: RMS-055
STATEMENT: RMS shall allow managing unique version identifiers for requirements (e.g., version number, timestamp).
REFERENCES: 5.6.2 Identification of config items
MALFORMED: No

[REQUIREMENT]
UID: RMS-056
STATEMENT: RMS shall allow retrieving and tracing specific versions of requirements.
REFERENCES: 5.6.2 Identification of config items
MALFORMED: No

[REQUIREMENT]
UID: RMS-057
STATEMENT: RMS shall allow check-in/check-out of baseline requirements for controlled updates.
REFERENCES: 5.6.3 Change management
MALFORMED: No

[REQUIREMENT]
UID: RMS-058
STATEMENT: RMS shall allow managing change requests with electronic forms and templates.
REFERENCES: 5.6.3 Change management
MALFORMED: No

[REQUIREMENT]
UID: RMS-059
STATEMENT: RMS shall allow notifying stakeholders electronically of approved changes.
REFERENCES: 5.6.3 Change management
MALFORMED: No

[REQUIREMENT]
UID: RMS-060
STATEMENT: RMS shall allow generating modification history reports including author, date, and change status.
REFERENCES: 5.6.3 Change management
MALFORMED: No

[REQUIREMENT]
UID: RMS-061
STATEMENT: RMS shall allow storing and managing references and links to source documents.
REFERENCES: 5.6.4 Traceability management
MALFORMED: No

[REQUIREMENT]
UID: RMS-062
STATEMENT: RMS shall allow generating reports comparing requirements before and after source updates.
REFERENCES: 5.6.4 Traceability management
MALFORMED: No

[REQUIREMENT]
UID: RMS-063
STATEMENT: RMS shall allow maintaining requirement-to-risk relationships.
REFERENCES: 5.6.5 Risk management
MALFORMED: No

[REQUIREMENT]
UID: RMS-064
STATEMENT: RMS shall allow recording requirements status for project management reporting.
REFERENCES: 5.6.6 Project management
MALFORMED: No

[REQUIREMENT]
UID: RMS-065
STATEMENT: RMS shall allow exchanging requirements status with external project management tools.
REFERENCES: 5.6.6 Project management
MALFORMED: No

[REQUIREMENT]
UID: RMS-066
STATEMENT: RMS shall allow simultaneous multi-user access to requirements with role-based access control.
REFERENCES: 5.7.2 Collaborative access
MALFORMED: No

[REQUIREMENT]
UID: RMS-067
STATEMENT: RMS shall allow assigning roles and access rights to users, groups, attributes, and tasks.
REFERENCES: 5.7.2 Collaborative access
MALFORMED: No

[REQUIREMENT]
UID: RMS-068
STATEMENT: RMS shall maintain data integrity under concurrent multi-user access.
REFERENCES: 5.7.2 Collaborative access
MALFORMED: No

[REQUIREMENT]
UID: RMS-069
STATEMENT: RMS shall provide project information including project size, concurrent users, and analyst roles.
REFERENCES: 5.7.3 Administrative information
MALFORMED: Yes

[REQUIREMENT]
UID: RMS-070
STATEMENT: RMS shall provide information on supported operating systems, databases, and hardware requirements.
REFERENCES: 5.7.3 Administrative information
MALFORMED: Yes

[REQUIREMENT]
UID: RMS-071
STATEMENT: RMS shall provide a graphical user interface with interactive input and editing of requirements.
REFERENCES: 5.7.4 GUI
MALFORMED: No

[REQUIREMENT]
UID: RMS-072
STATEMENT: RMS shall allow multiple synchronized views of requirements across windows.
REFERENCES: 5.7.4 GUI
MALFORMED: No

[REQUIREMENT]
UID: RMS-073
STATEMENT: RMS shall allow undo, cut, copy, and paste functions in requirement editing.
REFERENCES: 5.7.4 GUI
MALFORMED: Yes

[REQUIREMENT]
UID: RMS-074
STATEMENT: RMS shall allow access to requirements through a web browser interface.
REFERENCES: 5.7.4 GUI
MALFORMED: No

[REQUIREMENT]
UID: RMS-075
STATEMENT: RMS shall allow importing and exporting requirements to and from external tools (design, verification, project management).
REFERENCES: 5.2.8, 5.3.5, 5.5.3
MALFORMED: No

[REQUIREMENT]
UID: RMS-076
STATEMENT: RMS shall allow detection of ambiguous terms in requirements based on a user-defined list.
REFERENCES: 6.3.5 Non-ambiguity
MALFORMED: Yes

[REQUIREMENT]
UID: RMS-077
STATEMENT: RMS shall allow detection of unverifiable terms in requirements based on a user-defined list.
REFERENCES: 6.3.9 Verifiability
MALFORMED: Yes

[REQUIREMENT]
UID: RMS-078
STATEMENT: RMS shall allow stakeholders to define and review requirement priorities.
REFERENCES: 6.3.8 Priority
MALFORMED: No

[REQUIREMENT]
UID: RMS-079
STATEMENT: RMS shall allow requirements to be classified by compliance level (mandatory, objective).
REFERENCES: 6.3.7 Compliancy
MALFORMED: No

[REQUIREMENT]
UID: RMS-080
STATEMENT: RMS shall allow checking requirements for conciseness.
REFERENCES: 6.3.4 Conciseness
MALFORMED: Yes

[REQUIREMENT]
UID: RMS-081
STATEMENT: RMS shall allow users to associate each requirement with rationale for sufficiency and necessity.
REFERENCES: 6.3.13 Sufficiency & 6.3.14 Necessity
MALFORMED: Yes

[REQUIREMENT]
UID: RMS-082
STATEMENT: RMS shall allow requirements to be traced backward to sources and forward to design, verification, and tests.
REFERENCES: 6.3.6 Traceability
MALFORMED: No

[REQUIREMENT]
UID: RMS-083
STATEMENT: RMS shall allow stakeholders to manage glossaries and detect non-uniform use of terms.
REFERENCES: 6.3.16 Uniformity
MALFORMED: No

[REQUIREMENT]
UID: RMS-084
STATEMENT: RMS shall allow users to trace potentially duplicated requirements and report on uniqueness.
REFERENCES: 6.3.19 Uniqueness
MALFORMED: No

[REQUIREMENT]
UID: RMS-085
STATEMENT: RMS shall allow flagging requirements with frequent changes to identify unstable requirements.
REFERENCES: 6.3.12 Stability
MALFORMED: No

[REQUIREMENT]
UID: RMS-086
STATEMENT: RMS shall allow recording and reporting on each requirement's quality characteristics status (traceability, verifiability, etc.).
REFERENCES: 6.3.1 Overview
MALFORMED: No

[REQUIREMENT]
UID: RMS-087
STATEMENT: RMS shall allow linking affordability constraints (time, cost) to requirements and storing infeasible requirements for later use.
REFERENCES: 6.3.22 Affordability
MALFORMED: Yes
